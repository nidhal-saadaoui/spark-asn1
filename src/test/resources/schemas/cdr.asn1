-- Telecom CDR schema from SNidhal/ASN1SparkDatasource (simpleTypes.asn)
-- Uses APPLICATION class tags with IMPLICIT encoding.
GenericCDR-Schema DEFINITIONS IMPLICIT TAGS ::=
BEGIN
  GenericCallDataRecord ::= SEQUENCE {
    recordNumber   [APPLICATION 2]  IMPLICIT INTEGER,
    callingNumber  [APPLICATION 8]  IMPLICIT UTF8String,
    calledNumber   [APPLICATION 9]  IMPLICIT UTF8String,
    startDate      [APPLICATION 16] IMPLICIT UTF8String,
    startTime      [APPLICATION 18] IMPLICIT UTF8String,
    duration       [APPLICATION 19] IMPLICIT INTEGER
  }
END
