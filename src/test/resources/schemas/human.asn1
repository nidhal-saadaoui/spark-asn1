-- Nested SEQUENCE schema from SNidhal/ASN1SparkDatasource (nestedExample.asn)
-- Uses AUTOMATIC TAGS with an inline nested SEQUENCE.
World-Schema DEFINITIONS AUTOMATIC TAGS ::=
BEGIN
  Human ::= SEQUENCE {
    foo  SEQUENCE {
      bar INTEGER
    },
    name UTF8String OPTIONAL,
    age  INTEGER    OPTIONAL
  }
END
