RealModule DEFINITIONS AUTOMATIC TAGS ::= BEGIN

  Measurement ::= SEQUENCE {
    id    INTEGER,
    value REAL,
    label UTF8String
  }

  -- REAL inside CHOICE
  NumericValue ::= CHOICE {
    intVal  INTEGER,
    realVal REAL,
    strVal  UTF8String
  }

  NumericRecord ::= SEQUENCE {
    id  INTEGER,
    val NumericValue
  }

  -- REAL inside SEQUENCE OF
  Readings ::= SEQUENCE {
    id     INTEGER,
    values SEQUENCE OF REAL
  }

END
